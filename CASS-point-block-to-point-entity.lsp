(defun C:CASS2POINT ()
;  (setq ss (ssget "X" '((0 . "insert") (8 . "GCD"))))
(setq ss (ssget "X" '((0 . "insert") (2 . "GC*"))))
  (setq i 0)
  (repeat (sslength ss)
    (setq ssn (ssname ss i))
    (setq endata (entget ssn))
    (setq blockXYZ (assoc 10 endata))
    (print blockXYZ)
    (entmakeX (list '(0 . "POINT") blockXYZ))
    (setq i (1+ i))
    (entdel ssn)
  )
)
